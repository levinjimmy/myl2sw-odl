module myl2sw {
    yang-version 1.1;
    namespace "urn:opendaylight:params:xml:ns:yang:myl2sw";
    prefix "myl2sw";

    revision "2017-08-30" { // TODO change revision to date of model creation
        description "Initial revision of myl2sw model";
    }
}
